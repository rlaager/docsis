DOCS-CABLE-DEVICE-TRAP-MIB DEFINITIONS ::= BEGIN

IMPORTS
        MODULE-IDENTITY,
        NOTIFICATION-TYPE,
	OBJECT-TYPE
                FROM SNMPv2-SMI
        MODULE-COMPLIANCE,
        NOTIFICATION-GROUP,
	OBJECT-GROUP
                FROM SNMPv2-CONF
        docsDev,
--      docsDevBase,
        docsDevEvLevel,
        docsDevEvId,
        docsDevEvText,
        docsDevNotification
                FROM DOCS-CABLE-DEVICE-MIB  -- RFC2669
        docsIfCmtsCmStatusMacAddress
                FROM DOCS-IF-MIB            -- RFC2670
        docsIfDocsisCapability,
        docsIfDocsisOperMode,
        docsIfCmtsCmStatusDocsisMode
                FROM DOCS-IF-EXT-MIB
        ifPhysAddress
                FROM IF-MIB;
docsDevTrapMIB MODULE-IDENTITY
        LAST-UPDATED        "200009260000Z"
        ORGANIZATION        "Cisco Systems, Inc."
        CONTACT-INFO        "
                      Junming Gao
                      Cisco Systems Inc
                      <jgao@cisco.com>
                              "
        DESCRIPTION
                "CABLE DEVICE TRAP MIB is an extension of the
                 CABLE DEVICE MIB defined in RFC2669.
                  It defines various trap objects for both cable
                 modem and cable modem termination system.
                  There are two groups of SNMP notification objects are defined.
                 One group is for notifying cable modem events and one group
                 for notifying cable modem termination system events.
                  Common to all CM notification objects (traps) is that
                 in their OBJECTS statements, A CM trap contains information
                 about the event priority, the event Id, the event message
                 body, the CM DOCSIS capability, the CM DOCSIS register registration status,
                 the cable interface MAC address of the cable modem and
                 the cable card MAC address of the CMTS to which the modem is
                 connected to.
                  These objects are docsDevEvLevel, docsDevId, docsDevEvText,
                 docsIfDocsisCapability, docsIfDocsisOperMode,
                 ifPhysAddress and docsIfCmCmtsAddress. The values of
                 docsDevEvLevel, docsDevId, and docsDevEvText are from
                 the entry which logs this event in the
                 docsDevEventTable, which is defined in
                 DOCS-CABLE-DEVICE-MIB of RFC2669. The docsIfDocsisCapability
                 and docsIfDocsisOperMode are defined in DOCS-IF-EXT-MIB.
                 The ifPhysAddress value is the MAC address of the cable
                 interface of this cable modem. The docsIfCmCmtsAddress
                 specifies the MAC address of the CMTS (if there is a cable
                 card/interface in the CMTS, then it is actually the
                 cable interface interface MAC address to which the CM is connected).
                  Individual CM trap may contain additional objects to
                 provide necessary information.
                  Common to all CMTS notification objects (traps) is that
                 in their OBJECTS statements, A CMTS trap contains information
                 about the event priority, the event Id, the event message
                 body,  the connected CM DOCSIS register status, the CM cable
                 interface MAC address, the CMTS DOCSIS register status and
                 the CMTS MAC address.
                  These objects are docsDevEvLevel, docsDevId, docsDevEvText,
                 docsIfCmtsCmStatusDocsisMode, docsIfCmtsCmStatusMacAddress,
                 docsIfDocsisCapability, and ifPhysAddress. The values of
                 docsDevEvLevel, docsDevId, and docsDevEvText are
                 similar to what in CM traps. The values of
                 docsIfCmtsCmStatusDocsisMode and
                 docsIfCmtsCmStatusMacAddress are from the
                 docsIfCmtsCmStatusEntry (defined in DOCS-IF-MIB)
                 corresponding to a conneced CM. The docsIfDocsisCapability
                 indicates the CMTS DOCSIS capability.
                 The ifPhysAddress value is the CMTS MAC address (if there
                 is a cable card/interface in the CMTS, then it is actually
                 the MAC address of the cable interface which connected to the CM).
    "
        ::= { docsDev 10 }
--
-- docsDevNotification OBJECT IDENTIFIER   ::= { docsDev 2 }
--
docsDevTraps       OBJECT IDENTIFIER   ::= { docsDevNotification 1 }
docsDevTrapControl OBJECT IDENTIFIER   ::= { docsDevTraps 1}
docsDevTraps3      OBJECT IDENTIFIER   ::= { docsDevTraps 3 }
docsDevCmtsTraps   OBJECT IDENTIFIER   ::= { docsDevTraps3 0 }

docsDevCmtsTrapControl     OBJECT-TYPE
          SYNTAX     BITS {
             cmtsInitRegReqFailTrap(0),
             cmtsInitRegRspFailTrap(1),
             cmtsInitRegAckFailTrap(2),
             cmtsDynServReqFailTrap(3),
             cmtsDynServRspFailTrap(4),
             cmtsDynServAckFailTrap(5),
             cmtsBpiInitTrap(6),
             cmtsBPKMTrap(7),
             cmtsDynamicSATrap(8),
             cmtsDCCReqFailTrap(9),
             cmtsDCCRspFailTrap(10),
             cmtsDCCAckFailTrap(11)
             }
             MAX-ACCESS read-write
             STATUS  current
             DESCRIPTION
                 "The object is used to enable CMTS traps. From right to left,
                  the set bit indicates the corresponding CMTS trap is enabled.
                  For example, if the first bit is set, then
                  docsDevCmtsInitRegRspFailTrap is enabled. If it is zero,
                  the trap is disabled.
                 "
         ::= { docsDevTrapControl 2 }

docsDevCmtsInitRegReqFailTrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                    "An event to report the failure of a registration
                     request from CM happened during the CM initialization
                     process and detected in the CMTS side.

                     The values of docsDevEvLevel, docsDevId, and
                     docsDevEvText are from the entry which logs this event
                     in the docsDevEventTable. DocsIfCmtsCmStatusDocsisMode
                     and docsIfCmtsCmStatusMacAddress indicate the docsis
                     version and the MAC address of the requesting CM.
                     docsIfDocsisCapability and ifPhysAddress indicate
                     the docsis version of the CMTS and the MAC address
                     of the CMTS (if there is a cable card/interface in the
                     CMTS, then it is actually the MAC address of the cable
                     interface which connected to the CM)cable card connected
                     to the CM.

                     This part of information is uniformed across all CMTS traps.
                    "
         ::= { docsDevCmtsTraps 1 }

docsDevCmtsInitRegRspFailTrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                    "An event to report the failure of a registration
                     response happened during the CM initialization
                     process and detected in the CMTS side.
                    "
         ::= { docsDevCmtsTraps 2 }

docsDevCmtsInitRegAckFailTrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                    "An event to report the failure of a registration
                     acknowledgement from CM happened during the CM
                     initialization process and detected in the CMTS side.
                    "
        ::= { docsDevCmtsTraps 3 }


docsDevCmtsDynServReqFailTrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                 "An event to report the failure of a dynamic service
                  request happened during the dynamic services process
                  and detected in the CMTS side.
                 "
         ::= { docsDevCmtsTraps 4 }


docsDevCmtsDynServRspFailTrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                 "An event to report the failure of a dynamic service
                  response happened during the dynamic services process
                  and detected in the CMTS side.
                 "
         ::= { docsDevCmtsTraps 5 }

docsDevCmtsDynServAckFailTrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                 "An event to report the failure of a dynamic service
                  acknowledgement happened during the dynamic services
                  process and detected in the CMTS side.
                 "
         ::= { docsDevCmtsTraps 6 }

docsDevCmtsBpiInitTrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                 "An event to report the failure of a BPI initialization
                  attempt happened during the CM registration process
                  and detected in the CMTS side.
                 "
         ::= { docsDevCmtsTraps 7 }


docsDevCmtsBPKMTrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                 "An event to report the failure of a BPKM operation
                  which is detected in the CMTS side.
                 "
         ::= { docsDevCmtsTraps 8 }


docsDevCmtsDynamicSATrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                 "An event to report the failure of a dynamic security
                  association operation which is detected in the CMTS side.
                 "
         ::= { docsDevCmtsTraps 9 }

docsDevCmtsDCCReqFailTrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                 "An event to report the failure of a dynamic channel
                  change request happened during the dynamic channel
                  change process in the CM side and detected in the
                  CMTS side.
                 "
         ::= { docsDevCmtsTraps 10 }


docsDevCmtsDCCRspFailTrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                 "An event to report the failure of a dynamic channel
                  change response happened during the dynamic channel
                  change process in the CMTS side.
                 "
         ::= { docsDevCmtsTraps 11 }


docsDevCmtsDCCAckFailTrap    NOTIFICATION-TYPE
             OBJECTS { docsDevEvLevel,
                       docsDevEvId,
                       docsDevEvText,
                       docsIfCmtsCmStatusDocsisMode,
                       docsIfCmtsCmStatusMacAddress,
                       docsIfDocsisCapability,
                       ifPhysAddress }
             STATUS  current
             DESCRIPTION
                 "An event to report the failure of a dynamic channel
                  change acknowledgement happened during the dynamic channel
                  change process in the CMTS side.
                 "
         ::= { docsDevCmtsTraps 12}


--
-- Conformance definitions
--
docsDevTrapConformance  OBJECT IDENTIFIER   ::= { docsDevTraps 2 }
docsDevTrapGroups       OBJECT IDENTIFIER   ::= { docsDevTrapConformance 1 }
docsDevTrapCompliances  OBJECT IDENTIFIER   ::= { docsDevTrapConformance 2 }

docsDevCmtsTrapCompliance MODULE-COMPLIANCE
           STATUS  current
           DESCRIPTION
               "The compliance statement for MCNS Cable Modems and
                Cable Modem Termination Systems."

   MODULE  -- docsDevTrap

-- mandatory groups

GROUP docsDevCmtsTrapControlGroup
        DESCRIPTION
            "Mandatory in CMTS."

GROUP docsDevCmtsNotificationGroup
        DESCRIPTION
            "Mandatory in Cable Modem Termination Systems."

         ::= { docsDevTrapCompliances 2 }

docsDevCmtsTrapControlGroup OBJECT-GROUP
        OBJECTS {
             docsDevCmtsTrapControl
                     }
        STATUS      current
        DESCRIPTION
            "CMTS must support docsDevCmtsTrapControl."
        ::= { docsDevTrapGroups 3 }


docsDevCmtsNotificationGroup NOTIFICATION-GROUP
        NOTIFICATIONS {
             docsDevCmtsInitRegReqFailTrap,
             docsDevCmtsInitRegRspFailTrap,
             docsDevCmtsInitRegAckFailTrap ,
             docsDevCmtsDynServReqFailTrap,
             docsDevCmtsDynServRspFailTrap,
             docsDevCmtsDynServAckFailTrap,
             docsDevCmtsBpiInitTrap,
             docsDevCmtsBPKMTrap,
             docsDevCmtsDynamicSATrap,
             docsDevCmtsDCCReqFailTrap,
             docsDevCmtsDCCRspFailTrap,
             docsDevCmtsDCCAckFailTrap
           }
        STATUS      current
        DESCRIPTION
            "A collection of CMTS notifications providing device status and
             control."
        ::= { docsDevTrapGroups 4 }

END
