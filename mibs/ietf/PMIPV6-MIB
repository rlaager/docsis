PMIPV6-MIB DEFINITIONS ::= BEGIN
   IMPORTS
     MODULE-IDENTITY,  mib-2, Integer32, Counter32, Gauge32,
     Unsigned32, OBJECT-TYPE, NOTIFICATION-TYPE
                FROM SNMPv2-SMI                   -- RFC 2578
     PhysAddress, TimeStamp,
     TruthValue
                FROM SNMPv2-TC                    -- RFC 2579
     MODULE-COMPLIANCE, OBJECT-GROUP, NOTIFICATION-GROUP
                FROM SNMPv2-CONF                  -- RFC 2580
     InetAddressType, InetAddress, InetAddressPrefixLength
                FROM INET-ADDRESS-MIB             -- RFC 4001
     Ipv6AddressIfIdentifierTC
                FROM IP-MIB                       -- RFC 4293
     mip6MnBLEntry, mip6BindingCacheEntry
                FROM MOBILEIPV6-MIB               -- RFC 4295
     Pmip6TimeStamp64,    Pmip6MnIdentifier,
     Pmip6MnLLIdentifier, Pmip6MnIndex, Pmip6MnLLIndex,
     Pmip6MnInterfaceATT
                FROM PMIPV6-TC-MIB                -- RFC 6475
     ;

   pmip6MIB MODULE-IDENTITY
      LAST-UPDATED "201205070000Z"        --  7th May, 2012
      ORGANIZATION "IETF NETLMM Working Group"
      CONTACT-INFO
          "             Glenn Mansfield Keeni
                Postal: Cyber Solutions, Inc.
                        6-6-3, Minami Yoshinari
                        Aoba-ku, Sendai 989-3204, Japan.

                   Tel: +81-22-303-4012
                   Fax: +81-22-303-4015
                 EMail: glenn@cysols.com

                        Kazuhide Koide
                Postal: KDDI Corporation
                        GARDEN AIR TOWER 3-10-10, Iidabashi
                        Chiyoda-ku, Tokyo 102-8460, Japan.
                   Tel: +81-3-6678-3378
                 EMail: ka-koide@kddi.com

                        Sri Gundavelli
                Postal: Cisco
                        170 W.Tasman Drive,
                        San Jose, CA 95134
                        USA
                   Tel: +1-408-527-6109
                 EMail: sgundave@cisco.com

                        Ryuji Wakikawa
                Postal: TOYOTA InfoTechnology Center, U.S.A., Inc.
                        465 Bernardo Avenue
                        Mountain View, CA
                        94043
                        USA
                 EMail: ryuji@us.toyota-itc.com

         Support Group EMail: netlmm@ietf.org"

         DESCRIPTION
          "The MIB module for monitoring and controlling PMIPv6
           entities.

           Copyright (c) 2012 IETF Trust and the persons
           identified as authors of the code. All rights
           reserved.

           Redistribution and use in source and binary forms,
           with or without modification, is permitted pursuant
           to, and subject to the license terms contained in,
           the Simplified BSD License set forth in Section 4.c
           of the IETF Trust's Legal Provisions Relating to IETF
           Documents (http://trustee.ietf.org/license-info).
          "

          REVISION    "201205070000Z"      -- 7th May 2012
          DESCRIPTION "Initial version, published as RFC 6475."
       ::= { mib-2  206 }


   -- The PMIPv6 MIB has the following 5 primary groups

   pmip6Notifications     OBJECT IDENTIFIER ::= { pmip6MIB 0 }
   pmip6Objects           OBJECT IDENTIFIER ::= { pmip6MIB 1 }
   pmip6Conformance       OBJECT IDENTIFIER ::= { pmip6MIB 2 }
   pmip6Core              OBJECT IDENTIFIER ::= { pmip6Objects 1 }
   pmip6Mag               OBJECT IDENTIFIER ::= { pmip6Objects 2 }
   pmip6Lma               OBJECT IDENTIFIER ::= { pmip6Objects 3 }

    -- The sub groups

   pmip6System            OBJECT IDENTIFIER ::= { pmip6Core 1 }
   pmip6Bindings          OBJECT IDENTIFIER ::= { pmip6Core 2 }
   pmip6Conf              OBJECT IDENTIFIER ::= { pmip6Core 3 }
   pmip6Stats             OBJECT IDENTIFIER ::= { pmip6Core 4 }

   pmip6MagSystem         OBJECT IDENTIFIER ::= { pmip6Mag 1 }
   pmip6MagConf           OBJECT IDENTIFIER ::= { pmip6Mag 2 }
   pmip6MagRegistration   OBJECT IDENTIFIER ::= { pmip6Mag 3 }

   pmip6LmaSystem         OBJECT IDENTIFIER ::= { pmip6Lma 1 }
   pmip6LmaConf           OBJECT IDENTIFIER ::= { pmip6Lma 2 }

   -- The pmip6Stats group has the following sub groups

   pmip6BindingRegCounters OBJECT IDENTIFIER ::= { pmip6Stats 1 }

   --
   --
   -- pmip6System group
   --
   --
   pmip6Capabilities OBJECT-TYPE
       SYNTAX      BITS {
            mobilityAccessGateway  (0),
            localMobilityAnchor    (1)
                   }
       MAX-ACCESS  read-only
       STATUS      current
       DESCRIPTION
           "This object indicates the PMIPv6 functions that
            are supported by this managed entity.  Multiple
            Proxy Mobile IPv6 functions may be supported by
            a single entity.
            mobilityAccessGateway(0) indicates the availability
            of the mobility access gateway function.
            localMobilityAnchor(1) indicates the availability
            of the local mobility anchor function.


           "
       REFERENCE
               "RFC 6275: Sections 3.2, 4.1"
       ::= { pmip6System 1 }

   pmip6MobileNodeGeneratedTimestampInUse OBJECT-TYPE
       SYNTAX      TruthValue
       MAX-ACCESS  read-write
       STATUS      current
       DESCRIPTION
           "This flag indicates whether or not the
            MN-generated timestamp mechanism is in use in that
            Proxy Mobile IPv6 domain.
            true(1) indicates that the local mobility anchors and
            mobile access gateways in that Proxy Mobile IPv6
            domain apply the MN-generated timestamp considerations.
            false(0) indicates that the MN-generated timestamp
            mechanism is not in use in that Proxy Mobile IPv6
            domain.
            The default value for this flag is 'false'.
           "
       REFERENCE
           "RFC 5213: Sections 5.5, 9.3"
       DEFVAL { false }
       ::= { pmip6Conf 1 }
   pmip6FixedMagLinkLocalAddressOnAllAccessLinksType OBJECT-TYPE
       SYNTAX      InetAddressType
       MAX-ACCESS  read-write
       STATUS      current
       DESCRIPTION
           "The InetAddressType of the
            pmip6FixedMagLinkLocalAddressOnAllAccessLinks
            that follows.
           "
          ::= { pmip6Conf 2 }

   pmip6FixedMagLinkLocalAddressOnAllAccessLinks OBJECT-TYPE
       SYNTAX      InetAddress
       MAX-ACCESS  read-write
       STATUS      current
       DESCRIPTION
           "This variable indicates the link-local address value
            that all the mobile access gateways should use on
            any of the access links shared with any of the
            mobile nodes in that Proxy Mobile IPv6 domain.  If
            this variable is initialized with all zeroes, it
            implies that the use of fixed link-local address mode
            is not enabled for that Proxy Mobile IPv6 domain."


       REFERENCE
           "RFC 5213: Sections 2.2, 6.8, 6.9.1.1, 6.9.3, 9.3"
       ::= { pmip6Conf 3 }

   pmip6FixedMagLinkLayerAddressOnAllAccessLinks OBJECT-TYPE
       SYNTAX      PhysAddress
       MAX-ACCESS  read-write
       STATUS      current
       DESCRIPTION
           "This variable indicates the link-layer address value
            that all the mobile access gateways should use on
            any of the access links shared with any of the mobile
            nodes in that Proxy Mobile IPv6 domain.  For access
            technologies where there is no link-layer address,
            this variable MUST be initialized with all zeroes.
           "
       REFERENCE
           "RFC 5213: Sections 6.9.3, 9.3"
       ::= { pmip6Conf 4 }
   pmip6MagStatus OBJECT-TYPE
       SYNTAX      INTEGER { enabled(1), disabled(2) }
       MAX-ACCESS  read-write
       STATUS      current
       DESCRIPTION
           "This object indicates whether the PMIPv6 mobile
            access gateway function is enabled for the managed
            entity.

            Changing the status from enabled(1) to disabled(2)
            will terminate the PMIPv6 mobile access gateway
            function.  On the other hand, changing the status
            from disabled(2) to enabled(1) will start the PMIPv6
            mobile access gateway function.

            The value of this object MUST remain unchanged
            across reboots of the managed entity.
           "
       DEFVAL { disabled }
       ::= { pmip6MagSystem 1 }

   pmip6MagProxyCOATable OBJECT-TYPE
       SYNTAX      SEQUENCE OF Pmip6MagProxyCOAEntry
       MAX-ACCESS  not-accessible
       STATUS      current
       DESCRIPTION
           "This table models the Proxy Care-of Addresses
            configured on the egress interfaces of the mobile access
            gateway.  This address is the transport endpoint of the


            tunnel between the local mobility anchor and the mobile
            access gateway.

            Entries in this table are not required to survive
            a reboot of the managed entity.
           "
       REFERENCE
           "RFC 5213: Sections 2.2, 6.10"
       ::= { pmip6MagSystem 2 }
   pmip6MagProxyCOAEntry OBJECT-TYPE
       SYNTAX      Pmip6MagProxyCOAEntry
       MAX-ACCESS  not-accessible
       STATUS      current
       DESCRIPTION
           "This entry represents a conceptual row in the
            Proxy-CoA table.  It represents a Proxy Care-of
            Address on the mobile access gateway.

            Implementers need to be aware that if the total
            number of octets in pmip6MagProxyCOA
            exceeds 113, then OIDs of column
            instances in this row will have more than 128
            sub-identifiers and cannot be accessed using
            SNMPv1, SNMPv2c, or SNMPv3.
           "
       INDEX  { pmip6MagProxyCOAType, pmip6MagProxyCOA }
       ::= { pmip6MagProxyCOATable 1 }

   Pmip6MagProxyCOAEntry ::=
       SEQUENCE {
        pmip6MagProxyCOAType   InetAddressType,
        pmip6MagProxyCOA       InetAddress,
        pmip6MagProxyCOAState  INTEGER
       }

   pmip6MagProxyCOAType OBJECT-TYPE
       SYNTAX      InetAddressType
       MAX-ACCESS  not-accessible
       STATUS      current
       DESCRIPTION
           "The InetAddressType of the pmip6MagProxyCOA
            that follows.
           "
       ::= { pmip6MagProxyCOAEntry 1 }
   pmip6MagProxyCOA OBJECT-TYPE
       SYNTAX      InetAddress
       MAX-ACCESS  not-accessible
       STATUS      current


       DESCRIPTION
           "The Proxy-CoA configured on the egress interface of the
            mobile access gateway.

            The type of the address represented by this object
            is specified by the corresponding
            pmip6MagProxyCOAType object.
           "
       REFERENCE
           "RFC 5213: Sections 2.2, 6.10"
       ::= { pmip6MagProxyCOAEntry 2 }

   pmip6MagProxyCOAState  OBJECT-TYPE
       SYNTAX      INTEGER {
                              unknown(1),
                              activated(2),
                              tunneled(3)
                      }
       MAX-ACCESS  read-only
       STATUS      current
       DESCRIPTION
           "This object indicates the state of the Proxy-CoA:
               unknown     -- The state of the Proxy-CoA
                              cannot be determined.
               activated   -- The Proxy-CoA is ready to establish
                              a tunnel.  This state SHOULD be
                              indicated when the MAG is up but has
                              no mobile node.
               tunneled    -- Bidirectional tunnel is established
                              using the Proxy-CoA.
           "
       ::= { pmip6MagProxyCOAEntry 3 }
   pmip6MagEnableMagLocalRouting OBJECT-TYPE
       SYNTAX      TruthValue
       MAX-ACCESS  read-write
       STATUS      current
       DESCRIPTION
           "This flag indicates whether or not the mobile access
            gateway is allowed to enable local routing of the
            traffic exchanged between a visiting mobile node and
            a correspondent node that is locally connected to one
            of the interfaces of the mobile access gateway.
            The correspondent node can be another visiting mobile
            node as well, or a local fixed node.
            true(1) indicates that the mobile access gateway routes
            the traffic locally.
            false(0) indicates that the mobile access gateway
            reverse tunnels all the traffic to the mobile node's


            local mobility anchor.

            The default value for this flag is 'false'.
           "
       REFERENCE
           "RFC 5213: Section 9.2"           DEFVAL { false }
       ::= { pmip6MagConf 1 }

   pmip6MagMnIdentifierTable OBJECT-TYPE
        SYNTAX      SEQUENCE OF Pmip6MagMnIdentifierEntry
        MAX-ACCESS  not-accessible
        STATUS      current
        DESCRIPTION
            "A table containing the identifiers of mobile nodes
             attached to the MAG.
             Entries in this table are not required to survive
             a reboot of the managed entity.
            "
        REFERENCE
            "RFC 5213: Sections 2.2, 6.1"
        ::= { pmip6MagConf 2 }

   pmip6MagMnIdentifierEntry OBJECT-TYPE
        SYNTAX      Pmip6MagMnIdentifierEntry
        MAX-ACCESS  not-accessible
        STATUS      current
        DESCRIPTION
            "An entry in the mobile node identifier table.
            "
        INDEX  { pmip6MagBLMnIndex
               }
        ::= { pmip6MagMnIdentifierTable 1 }

   Pmip6MagMnIdentifierEntry ::=
        SEQUENCE {
         pmip6MagMnIdentifier      Pmip6MnIdentifier
       }

   pmip6MagMnIdentifier  OBJECT-TYPE
        SYNTAX      Pmip6MnIdentifier
        MAX-ACCESS  read-only
        STATUS      current
        DESCRIPTION
            "The identity of a mobile node in the Proxy Mobile IPv6
             domain.
            "
       REFERENCE
           "RFC 5213: Sections 2.2, 6.1"


        ::= { pmip6MagMnIdentifierEntry 1 }

   pmip6MagMnLLIdentifierTable OBJECT-TYPE
        SYNTAX      SEQUENCE OF Pmip6MagMnLLIdentifierEntry
        MAX-ACCESS  not-accessible
        STATUS      current
        DESCRIPTION
            "A table containing the link-layer identifiers
             of the interfaces of the mobile nodes attached
             to the MAG.
             Entries in this table are not required to survive
             a reboot of the managed entity.
            "
        REFERENCE
            "RFC 5213: Sections 2.2, 6.1"
        ::= { pmip6MagConf 3 }

   pmip6MagMnLLIdentifierEntry OBJECT-TYPE
        SYNTAX      Pmip6MagMnLLIdentifierEntry
        MAX-ACCESS  not-accessible
        STATUS      current
        DESCRIPTION
            "An entry in the mobile node link-layer identifier
             table.
            "
        INDEX  { pmip6MagBLMnIndex, pmip6MagBLMnLLIndex
               }
        ::= { pmip6MagMnLLIdentifierTable 1 }

   Pmip6MagMnLLIdentifierEntry ::=
        SEQUENCE {
         pmip6MagMnLLIdentifier      Pmip6MnLLIdentifier
       }

   pmip6MagMnLLIdentifier  OBJECT-TYPE
        SYNTAX      Pmip6MnLLIdentifier
        MAX-ACCESS  read-only
        STATUS      current
        DESCRIPTION
            "The link-layer identifier of the mobile node's
             connected interface on the access link.
            "
        REFERENCE
            "RFC 5213: Sections 2.2, 6.1"
        ::= { pmip6MagMnLLIdentifierEntry 1 }

   pmip6MagHomeNetworkPrefixTable   OBJECT-TYPE
        SYNTAX      SEQUENCE OF Pmip6MagHomeNetworkPrefixEntry


        MAX-ACCESS  not-accessible
        STATUS      current
        DESCRIPTION
            "A table representing the home network prefixes
             assigned to the connected interfaces of mobile nodes
             attached to the MAG.
            "
        REFERENCE
            "RFC 5213: Sections 2, 6.1, 6.2"
        ::= { pmip6MagConf 4 }

   pmip6MagHomeNetworkPrefixEntry OBJECT-TYPE
        SYNTAX      Pmip6MagHomeNetworkPrefixEntry
        MAX-ACCESS  not-accessible
        STATUS      current
        DESCRIPTION
            "An entry in the home network prefixes table.

             Implementers need to be aware that if the total
             number of octets in pmip6MagHomeNetworkPrefix
             exceeds 111, then OIDs of column instances in
             this row will have more than 128 sub-identifiers
             and cannot be accessed using SNMPv1, SNMPv2c, or
             SNMPv3.
            "
        INDEX  { pmip6MagBLMnIndex, pmip6MagBLMnLLIndex,
                 pmip6MagHomeNetworkPrefixType,
                 pmip6MagHomeNetworkPrefix }
        ::= { pmip6MagHomeNetworkPrefixTable 1 }

   Pmip6MagHomeNetworkPrefixEntry ::=
        SEQUENCE {
         pmip6MagHomeNetworkPrefixType      InetAddressType,
         pmip6MagHomeNetworkPrefix          InetAddress,
         pmip6MagHomeNetworkPrefixLength    InetAddressPrefixLength,
         pmip6MagHomeNetworkPrefixLifeTime  Unsigned32
       }

   pmip6MagHomeNetworkPrefixType  OBJECT-TYPE
        SYNTAX      InetAddressType
        MAX-ACCESS  not-accessible
        STATUS      current
        DESCRIPTION
            "The InetAddressType of the pmip6MagHomeNetworkPrefix
             that follows.
            "
        ::= { pmip6MagHomeNetworkPrefixEntry 1 }



   pmip6MagHomeNetworkPrefix   OBJECT-TYPE
        SYNTAX      InetAddress
        MAX-ACCESS  not-accessible
        STATUS      current
        DESCRIPTION
            "The mobile network prefix that is delegated to the
             mobile node.  The type of the address represented by
             this object is specified by the corresponding
             pmip6MagHomeNetworkPrefixType object.
            "
        REFERENCE
            "RFC 5213: Section 2"
        ::= { pmip6MagHomeNetworkPrefixEntry 2 }

   pmip6MagHomeNetworkPrefixLength   OBJECT-TYPE
        SYNTAX      InetAddressPrefixLength
        MAX-ACCESS  read-only
        STATUS      current
        DESCRIPTION
            "The prefix length of the home network prefix.
            "
        ::= { pmip6MagHomeNetworkPrefixEntry 3 }

   pmip6MagHomeNetworkPrefixLifeTime   OBJECT-TYPE
        SYNTAX      Unsigned32
        UNITS       "seconds"
        MAX-ACCESS  read-only
        STATUS      current
        DESCRIPTION
            "The lifetime parameter (in seconds) that will be
             advertised in Router Advertisements by the MAG for
             this home network prefix.
            "
        REFERENCE
            "RFC 5213: Sections 6.2, 6.7"
        ::= { pmip6MagHomeNetworkPrefixEntry 4 }

   pmip6MagBLTable OBJECT-TYPE
       SYNTAX      SEQUENCE OF Pmip6MagBLEntry
       MAX-ACCESS  not-accessible
       STATUS      current
       DESCRIPTION
           "This table corresponds to the Binding Update List (BL)
            that includes PMIPv6-related information and is
            maintained by the mobile access gateway.
            Entries from the table are deleted as the lifetime of
            the binding expires.
           "


       REFERENCE
           "RFC 6275: Sections 4.5, 11.1
            RFC 5213: Section 6.1"
       ::= { pmip6MagRegistration 1 }
   pmip6MagBLEntry  OBJECT-TYPE
       SYNTAX      Pmip6MagBLEntry
       MAX-ACCESS  not-accessible
       STATUS      current
       DESCRIPTION
           "An entry containing additional information from
            a Binding Update sent by the mobile access gateway
            to the local mobility anchor.
           "
       AUGMENTS {mip6MnBLEntry}
       ::= { pmip6MagBLTable 1 }

   Pmip6MagBLEntry ::= SEQUENCE {
       pmip6MagBLFlag                    TruthValue,
       pmip6MagBLMnIndex                 Pmip6MnIndex,
       pmip6MagBLMnLLIndex               Pmip6MnLLIndex,
       pmip6MagBLMagLinkLocalAddressType InetAddressType,
       pmip6MagBLMagLinkLocalAddress     InetAddress,
       pmip6MagBLMagIfIdentifierToMn     Ipv6AddressIfIdentifierTC,
       pmip6MagBLTunnelIfIdentifier      Ipv6AddressIfIdentifierTC,
       pmip6MagBLMnInterfaceATT  Pmip6MnInterfaceATT,
       pmip6MagBLTimeRecentlyAccepted    Pmip6TimeStamp64
       }

   pmip6MagBLFlag OBJECT-TYPE
       SYNTAX      TruthValue
       MAX-ACCESS  read-only
       STATUS      current
       DESCRIPTION
           "true(1) indicates that the mobile access gateway sent
            the Proxy Binding Update with Proxy Registration Flag
            that indicates to the local mobility anchor that the
            registration is the Proxy Binding Update and is from a
            mobile access gateway.
            false(0) implies that the mobile access gateway is
            behaving as a simple mobile node.
           "
       REFERENCE
           "RFC 5213: Section 8.1"
       ::= { pmip6MagBLEntry 1 }

   pmip6MagBLMnIndex OBJECT-TYPE
       SYNTAX     Pmip6MnIndex
       MAX-ACCESS  read-only


       STATUS      current
       DESCRIPTION
           "The index to the identifier of the attached mobile
            node in the pmip6MagMnIdentifierTable.
           "
       REFERENCE
           "RFC 5213: Sections 2.2, 6.1, 8.1"
       ::= { pmip6MagBLEntry 2 }

   pmip6MagBLMnLLIndex OBJECT-TYPE
       SYNTAX      Pmip6MnLLIndex
       MAX-ACCESS  read-only
       STATUS      current
       DESCRIPTION
           "The index to the link-layer identifier of the mobile
            node's connected interface in the
            pmip6MagMnLLIdentifierTable.
           "
       REFERENCE
           "RFC 5213: Sections 2.2, 6.1, 8.1"
       ::= { pmip6MagBLEntry 3 }

   pmip6MagBLMagLinkLocalAddressType OBJECT-TYPE
       SYNTAX     InetAddressType
       MAX-ACCESS  read-only
       STATUS      current
       DESCRIPTION
           "The InetAddressType of the pmip6MagBLMagLinkLocalAddress
            that follows.
           "
       ::= { pmip6MagBLEntry 4 }

   pmip6MagBLMagLinkLocalAddress OBJECT-TYPE
       SYNTAX     InetAddress
       MAX-ACCESS  read-only
       STATUS      current
       DESCRIPTION
           "The link-local address of the mobile access gateway on
            the access link shared with the mobile node.
            This is the address that is present in the Link-local
            Address option of the corresponding Proxy Binding Update
            message.
           "
       REFERENCE
           "RFC 3963: Sections 4.1, 5.1"
       ::= { pmip6MagBLEntry 5 }

   pmip6MagBLMagIfIdentifierToMn OBJECT-TYPE


       SYNTAX     Ipv6AddressIfIdentifierTC
       MAX-ACCESS  read-only
       STATUS      current
       DESCRIPTION
           "The interface identifier (if-id) of the point-to-point
            link between the mobile node and the mobile access
            gateway.  This is internal to the mobile access gateway
            and is used to associate the Proxy Mobile IPv6 tunnel
            to the access link where the mobile node is attached.
           "
       REFERENCE
           "RFC 5213: Sections 6.1, 8.1"
       ::= { pmip6MagBLEntry 6 }

   pmip6MagBLTunnelIfIdentifier OBJECT-TYPE
       SYNTAX     Ipv6AddressIfIdentifierTC
       MAX-ACCESS  read-only
       STATUS      current
       DESCRIPTION
           "The tunnel interface identifier (tunnel-if-id) of the
            bidirectional tunnel between the mobile node's local
            mobility anchor and the mobile access gateway.  This
            is internal to the mobile access gateway.  The tunnel
            interface identifier is acquired during the tunnel
            creation.
           "
       REFERENCE
           "RFC 5213: Sections 6.1, 8.1"
       ::= { pmip6MagBLEntry 7 }

    pmip6MagBLMnInterfaceATT OBJECT-TYPE
       SYNTAX      Pmip6MnInterfaceATT
       MAX-ACCESS  read-only
       STATUS      current
       DESCRIPTION
           "The type of the access technology by which the mobile
            node is currently attached to the mobile access gateway.
           "
       REFERENCE
           "RFC 5213: Sections 6.9.1.1, 6.9.1.5, 8.1"
       ::= { pmip6MagBLEntry 8 }
    pmip6MagBLTimeRecentlyAccepted OBJECT-TYPE
       SYNTAX      Pmip6TimeStamp64
       MAX-ACCESS  read-only
       STATUS      current
       DESCRIPTION
           "The 64-bit timestamp value of the most recently
            accepted Proxy Binding Update message sent for this


            mobile node.  This is the time of day on the mobile
            access gateway, when the Proxy Binding Acknowledgement
            message with the Status field set to 0
            was received.  If the Timestamp option is not present
            in the Proxy Binding Update message (i.e., when the
            sequence-number-based scheme is in use), the value MUST
            be initialized with all zeroes.
           "
       REFERENCE
           "RFC 5213: Sections 5.1, 8.1"
       ::= { pmip6MagBLEntry 9 }

   pmip6MagMnProfileTable OBJECT-TYPE
       SYNTAX      SEQUENCE OF Pmip6MagMnProfileEntry
       MAX-ACCESS  not-accessible
       STATUS      current
       DESCRIPTION
           "This table corresponds to the mobile node's policy
            profile that includes the essential operational
            parameters that are required by the network entities
            for managing the mobile node's mobility service.
            It contains policy profiles of mobile nodes that are
            connected to the mobile access gateway.
            Entries in this table are not required to survive
            a reboot of the managed entity.
           "
       REFERENCE
           "RFC 5213: Section 6.2"
       ::= { pmip6MagRegistration 2 }

   pmip6MagMnProfileEntry  OBJECT-TYPE
       SYNTAX      Pmip6MagMnProfileEntry
       MAX-ACCESS  not-accessible
       STATUS      current
       DESCRIPTION
           "An entry containing information about the
            mobile node's policy profile.
           "
       INDEX { pmip6MagProfMnIndex }
       ::= { pmip6MagMnProfileTable 1 }

   Pmip6MagMnProfileEntry ::=
       SEQUENCE {
        pmip6MagProfMnIndex                      Pmip6MnIndex,
        pmip6MagProfMnIdentifier                 Pmip6MnIdentifier,
        pmip6MagProfMnLocalMobilityAnchorAddressType
                                                 InetAddressType,
        pmip6MagProfMnLocalMobilityAnchorAddress InetAddress


       }

   pmip6MagProfMnIndex OBJECT-TYPE
       SYNTAX      Pmip6MnIndex
       MAX-ACCESS  not-accessible
       STATUS      current
       DESCRIPTION
           "The index for a mobile node in the Proxy Mobile IPv6
            domain.
           "
       ::= { pmip6MagMnProfileEntry 1 }

   pmip6MagProfMnIdentifier OBJECT-TYPE
       SYNTAX      Pmip6MnIdentifier
       MAX-ACCESS  read-only
       STATUS      current
       DESCRIPTION
           "The identity of a mobile node in the Proxy Mobile IPv6
            domain.
           "
       REFERENCE
           "RFC 5213: Section 2.2"
       ::= { pmip6MagMnProfileEntry 2 }

   pmip6MagProfMnLocalMobilityAnchorAddressType OBJECT-TYPE
       SYNTAX     InetAddressType
       MAX-ACCESS  read-only
       STATUS      current
       DESCRIPTION
           "The InetAddressType of the
            pmip6MagMnLocalMobilityAnchorAddress that follows.
           "
       ::= { pmip6MagMnProfileEntry 3 }
   pmip6MagProfMnLocalMobilityAnchorAddress OBJECT-TYPE
       SYNTAX     InetAddress
       MAX-ACCESS  read-only
       STATUS      current
       DESCRIPTION
           "The global address that is configured on the interface
            of the local mobility anchor and is the transport
            endpoint of the bidirectional tunnel established
            between the local mobility anchor and the mobile access
            gateway.  This is the address to which the mobile
            access gateway sends the Proxy Binding Update messages.
           "
       REFERENCE
           "RFC 5213: Section 2.2"
       ::= { pmip6MagMnProfileEntry 4 }


   pmip6BindingCacheTable OBJECT-TYPE
       SYNTAX      SEQUENCE OF Pmip6BindingCacheEntry
       MAX-ACCESS  not-accessible
       STATUS      current
       DESCRIPTION
           "This table models the Binding Cache on the local
            mobility anchor.

            Entries from the table are deleted as the lifetime
            of the binding expires.

            Entries in this table are not required to survive
            a reboot of the managed entity.
           "
       REFERENCE
           "RFC 6275: Sections 4.5, 9.1, 10.1
            RFC 5213: Section 5.1"
       ::= { pmip6Bindings 1 }

   pmip6BindingCacheEntry  OBJECT-TYPE
       SYNTAX      Pmip6BindingCacheEntry
       MAX-ACCESS  not-accessible
       STATUS      current
       DESCRIPTION
           "An entry containing additional information contained
            in the Binding Cache table of the local mobility anchor.
           "
       AUGMENTS {mip6BindingCacheEntry}
   ::= { pmip6BindingCacheTable 1 }

   Pmip6BindingCacheEntry ::= SEQUENCE {
        pmip6BindingPBUFlag                 TruthValue,
        pmip6BindingMnIndex                 Pmip6MnIndex,
        pmip6BindingMnLLIndex               Pmip6MnLLIndex,
        pmip6BindingMagLinkLocalAddressType InetAddressType,
        pmip6BindingMagLinkLocalAddress     InetAddress,
        pmip6BindingTunnelIfIdentifier    Ipv6AddressIfIdentifierTC,
        pmip6BindingMnInterfaceATT
                                       Pmip6MnInterfaceATT,
        pmip6BindingTimeRecentlyAccepted     Pmip6TimeStamp64
       }

   pmip6BindingPBUFlag OBJECT-TYPE
       SYNTAX      TruthValue
       MAX-ACCESS  read-only
       STATUS      current
       DESCRIPTION
           "true(1) indicates that the local mobility anchor


            accepted the binding update with Proxy Registration
            Flag from a mobile access gateway.
            false(0) implies that the binding cache is from a
            mobile node.  In this case, the remaining objects will
            not be accessible.
           "
       REFERENCE
           "RFC 5213: Sections 5.1, 8.1"
       ::= { pmip6BindingCacheEntry 1 }

   pmip6BindingMnIndex OBJECT-TYPE
       SYNTAX      Pmip6MnIndex
       MAX-ACCESS  read-only
       STATUS      current
       DESCRIPTION
           "An index to the identifier of the registered mobile
            node.
           "
       REFERENCE
           "RFC 5213: Sections 2.2, 5.1, 8.1
            RFC 4283: Section 3"
       ::= { pmip6BindingCacheEntry 2 }
   pmip6BindingMnLLIndex OBJECT-TYPE
       SYNTAX      Pmip6MnLLIndex
       MAX-ACCESS  read-only
       STATUS      current
       DESCRIPTION
           "The index to the link-layer identifier of the mobile
            node's connected interface on the access link.
           "
       REFERENCE
           "RFC 5213: Sections 2.2, 5.1, 8.1"
       ::= { pmip6BindingCacheEntry 3 }

   pmip6BindingMagLinkLocalAddressType OBJECT-TYPE
       SYNTAX      InetAddressType
       MAX-ACCESS  read-only
       STATUS      current
       DESCRIPTION
           "The InetAddressType of the
            pmip6BindingMagLinkLocalAddress that follows.
           "
       ::= { pmip6BindingCacheEntry 4 }

   pmip6BindingMagLinkLocalAddress OBJECT-TYPE
       SYNTAX      InetAddress
       MAX-ACCESS  read-only
       STATUS      current


       DESCRIPTION
           "The link-local address of the mobile access gateway on
            the point-to-point link shared with the mobile node.
            This is generated by the local mobility anchor after
            accepting the initial Proxy Binding Update message.
            This is the address that is present in the Link-local
            Address option of the corresponding Proxy Binding
            Acknowledgement message.
           "
       REFERENCE
           "RFC 5213: Sections 5.1, 6.9.1.2, 8.2"
       ::= { pmip6BindingCacheEntry 5 }

   pmip6BindingTunnelIfIdentifier OBJECT-TYPE
       SYNTAX      Ipv6AddressIfIdentifierTC
       MAX-ACCESS  read-only
       STATUS      current
       DESCRIPTION
           "The tunnel interface identifier (tunnel-if-id) of the
            bidirectional tunnel between the local mobility anchor
            and the mobile access gateway where the mobile node is
            currently anchored.  This is internal to the local
            mobility anchor.  The tunnel interface identifier is
            acquired during the tunnel creation.
           "
       REFERENCE
           "RFC 5213: Sections 5.1, 8.1"
       ::= { pmip6BindingCacheEntry 6 }

   pmip6BindingMnInterfaceATT OBJECT-TYPE
       SYNTAX      Pmip6MnInterfaceATT
       MAX-ACCESS  read-only
       STATUS      current
       DESCRIPTION
           "The access technology type by which the mobile node
            is currently attached.  This is obtained from the
            Access Technology Type option, present in the Proxy
            Binding Update message.
           "
       REFERENCE
           "RFC 5213: Sections 5.1, 8.1"
       ::= { pmip6BindingCacheEntry 7 }

   pmip6BindingTimeRecentlyAccepted OBJECT-TYPE
       SYNTAX      Pmip6TimeStamp64
       MAX-ACCESS  read-only
       STATUS      current
       DESCRIPTION


           "The 64-bit timestamp value of the most recently
            accepted Proxy Binding Update message sent for this
            mobile node.  This is the time of day on the local
            mobility anchor, when the message was received.  If
            the Timestamp option is not present in the Proxy
            Binding Update message (i.e., when the sequence number
            based scheme is in use), the value MUST be initialized
            with all zeroes.
           "
       REFERENCE
           "RFC 5213: Sections 5.1, 8.1"
       ::= { pmip6BindingCacheEntry 8 }

   ---
   ---
   --- pmip6Stats group
   ---
   ---

   --
   -- pmip6Stats:pmip6BindingRegCounters
   --

   pmip6MissingMnIdentifierOption  OBJECT-TYPE
       SYNTAX      Counter32
       MAX-ACCESS  read-only
       STATUS      current
       DESCRIPTION
           "Total number of Proxy Binding Update messages
            rejected by the local mobility anchor with status
            code in the Binding Acknowledgement message indicating
            'Missing mobile node identifier option' (Code 160).

            Discontinuities in the value of this counter can
            occur at re-initialization of the mobile router,
            and at other times as indicated by the value of
            pmip6CounterDiscontinuityTime.
           "
       REFERENCE
           "RFC 5213: Sections 5.3.1, 8.9"
           ::= { pmip6BindingRegCounters 1 }

   pmip6MagNotAuthorizedForProxyReg OBJECT-TYPE
       SYNTAX      Counter32
       MAX-ACCESS  read-only
       STATUS      current
       DESCRIPTION
           "Total number of Proxy Binding Update messages


            rejected by the local mobility anchor with status
            code in the Binding Acknowledgement message indicating
            'Not authorized to send Proxy Binding Updates'
            (Code 154).

            Discontinuities in the value of this counter can
            occur at re-initialization of the mobile router,
            and at other times as indicated by the value of
            pmip6CounterDiscontinuityTime.
           "
       REFERENCE
           "RFC 5213: Sections 5.3.1, 8.9"
           ::= { pmip6BindingRegCounters 2 }

   pmip6NotLMAForThisMobileNode  OBJECT-TYPE
       SYNTAX      Counter32
       MAX-ACCESS  read-only
       STATUS      current
       DESCRIPTION
           "Total number of Proxy Binding Update messages rejected
            by the local mobility anchor with status code in the
            Binding Acknowledgement message indicating
            'Not local mobility anchor for this mobile node'
            (Code 153).

            Discontinuities in the value of this counter can
            occur at re-initialization of the management system,
            and at other times as indicated by the value of
            pmip6CounterDiscontinuityTime.
           "
       REFERENCE
           "RFC 5213: Sections 5.3.1, 8.9"
           ::= { pmip6BindingRegCounters 3 }

   pmip6ProxyRegNotEnabled  OBJECT-TYPE
       SYNTAX      Counter32
       MAX-ACCESS  read-only
       STATUS      current
       DESCRIPTION
           "Total number of Proxy Binding Update messages rejected
            by the local mobility anchor with status code in the
            Binding Acknowledgement message indicating
            'Proxy Registration not enabled' (Code 152).
            Discontinuities in the value of this counter can
            occur at re-initialization of the management system,
            and at other times as indicated by the value of
            pmip6CounterDiscontinuityTime.
           "


       REFERENCE
           "RFC 5213: Sections 5.3.1, 6.9.1.2, 8.9"
           ::= { pmip6BindingRegCounters 4 }
   pmip6MissingHomeNetworkPrefixOption  OBJECT-TYPE
       SYNTAX      Counter32
       MAX-ACCESS  read-only
       STATUS      current
       DESCRIPTION
           "Total number of Proxy Binding Update messages rejected
            by the local mobility anchor with status code in the
            Binding Acknowledgement message indicating
            'Missing home network prefix option' (Code 158).
            Discontinuities in the value of this counter can
            occur at re-initialization of the management system,
            and at other times as indicated by the value of
            pmip6CounterDiscontinuityTime.
           "
       REFERENCE
           "RFC 5213: Sections 5.3.1, 8.9"
           ::= { pmip6BindingRegCounters 5 }

   pmip6MissingHandOffIndicatorOption OBJECT-TYPE
       SYNTAX      Counter32
       MAX-ACCESS  read-only
       STATUS      current
       DESCRIPTION
           "Total number of Proxy Binding Update messages rejected
            by the local mobility anchor with status code in the
            Binding Acknowledgement message indicating
            'Missing handoff indicator option' (Code 161).
            Discontinuities in the value of this counter can
            occur at re-initialization of the management system,
            and at other times as indicated by the value of
            pmip6CounterDiscontinuityTime.
           "
       REFERENCE
           "RFC 5213: Sections 5.3.1, 8.9"
           ::= { pmip6BindingRegCounters 6 }

   pmip6MissingAccessTechTypeOption OBJECT-TYPE
       SYNTAX      Counter32
       MAX-ACCESS  read-only
       STATUS      current
       DESCRIPTION
           "Total number of Proxy Binding Update messages rejected
            by the local mobility anchor with status code in the
            Binding Acknowledgement message indicating
            'Missing access technology type option' (Code 162).


            Discontinuities in the value of this counter can
            occur at re-initialization of the management system,
            and at other times as indicated by the value of
            pmip6CounterDiscontinuityTime.
           "
       REFERENCE
           "RFC 5213: Sections 5.3.1, 8.9"
           ::= { pmip6BindingRegCounters 7 }

   pmip6NotAuthorizedForHomeNetworkPrefix OBJECT-TYPE
       SYNTAX      Counter32
       MAX-ACCESS  read-only
       STATUS      current
       DESCRIPTION
           "Total number of Proxy Binding Update messages rejected
            by the local mobility anchor with status code in the
            Binding Acknowledgement message indicating
            'Mobile node not authorized for one or more of the
            requesting home network prefixes' (Code 155).

            Discontinuities in the value of this counter can
            occur at re-initialization of the management system,
            and at other times as indicated by the value of
            pmip6CounterDiscontinuityTime.
           "
       REFERENCE
           "RFC 5213: Sections 5.3.2, 6.9.1.2, 8.9"
           ::= { pmip6BindingRegCounters 8 }

   pmip6TimestampMismatch OBJECT-TYPE
       SYNTAX      Counter32
       MAX-ACCESS  read-only
       STATUS      current
       DESCRIPTION
           "Total number of Proxy Binding Update messages rejected
            by the local mobility anchor with status code in the
            Binding Acknowledgement message indicating
            'Invalid timestamp value (the clocks are out of sync)'
            (Code 156).
            Discontinuities in the value of this counter can
            occur at re-initialization of the management system,
            and at other times as indicated by the value of
            pmip6CounterDiscontinuityTime.
           "
       REFERENCE
           "RFC 5213: Sections 5.5, 6.9.1.2, 8.9"
           ::= { pmip6BindingRegCounters 9 }



   pmip6TimestampLowerThanPrevAccepted OBJECT-TYPE
       SYNTAX      Counter32
       MAX-ACCESS  read-only
       STATUS      current
       DESCRIPTION
           "Total number of Proxy Binding Update messages rejected
            by the local mobility anchor with status code in the
            Binding Acknowledgement message indicating
            'The timestamp value is lower than the previously
            accepted value' (Code 157).
            Discontinuities in the value of this counter can
            occur at re-initialization of the management system,
            and at other times as indicated by the value of
            pmip6CounterDiscontinuityTime.
           "
       REFERENCE
           "RFC 5213: Sections 5.5, 6.9.1.2, 8.9"
           ::= { pmip6BindingRegCounters 10 }

   pmip6BcePbuPrefixSetDoNotMatch OBJECT-TYPE
       SYNTAX      Counter32
       MAX-ACCESS  read-only
       STATUS      current
       DESCRIPTION
           "Total number of Proxy Binding Update messages rejected
            by the local mobility anchor with status code in the
            Binding Acknowledgement message indicating
            'All the home network prefixes listed in the Binding
            Cache entry do not match all the prefixes in the
            received Proxy Binding Update' (Code 159).
            Discontinuities in the value of this counter can
            occur at re-initialization of the management system,
            and at other times as indicated by the value of
            pmip6CounterDiscontinuityTime.
           "
       REFERENCE
           "RFC 5213: Sections 5.4.1.1, 8.9"
           ::= { pmip6BindingRegCounters 11 }

   pmip6InitialBindingRegistrations OBJECT-TYPE
       SYNTAX      Counter32
       MAX-ACCESS  read-only
       STATUS      current
       DESCRIPTION
           "Total number of Proxy Binding Update messages that
            newly creates the Binding Cache entry.
            Discontinuities in the value of this counter can
            occur at re-initialization of the management system,


            and at other times as indicated by the value of
            pmip6CounterDiscontinuityTime.
           "
       REFERENCE
           "RFC 5213: Sections 5.3.2"
           ::= { pmip6BindingRegCounters 12 }

   pmip6BindingLifeTimeExtensionNoHandOff OBJECT-TYPE
       SYNTAX      Counter32
       MAX-ACCESS  read-only
       STATUS      current
       DESCRIPTION
           "Total number of Proxy Binding Update messages for
            extending the binding lifetime, received from the
            same mobile access gateway that last updated the
            binding.
            Discontinuities in the value of this counter can
            occur at re-initialization of the management system,
            and at other times as indicated by the value of
            pmip6CounterDiscontinuityTime.
           "
       REFERENCE
           "RFC 5213: Sections 5.3.3"
           ::= { pmip6BindingRegCounters 13 }

   pmip6BindingLifeTimeExtensionAfterHandOff OBJECT-TYPE
       SYNTAX      Counter32
       MAX-ACCESS  read-only
       STATUS      current
       DESCRIPTION
           "Total number of Proxy Binding Update messages for
            extending the binding lifetime, received from a new
            mobile access gateway where the mobile node's
            mobility session is handed off.
            Discontinuities in the value of this counter can
            occur at re-initialization of the management system,
            and at other times as indicated by the value of
            pmip6CounterDiscontinuityTime.
           "
       REFERENCE
           "RFC 5213: Sections 5.3.4"
           ::= { pmip6BindingRegCounters 14 }

   pmip6BindingDeRegistrations OBJECT-TYPE
       SYNTAX      Counter32
       MAX-ACCESS  read-only
       STATUS      current
       DESCRIPTION


           "Total number of Proxy Binding Update messages with
            the lifetime value of zero.
            Discontinuities in the value of this counter can
            occur at re-initialization of the management system,
            and at other times as indicated by the value of
            pmip6CounterDiscontinuityTime.
           "
       REFERENCE
           "RFC 5213: Sections 5.3.5"
           ::= { pmip6BindingRegCounters 15 }

   pmip6BindingBindingAcks OBJECT-TYPE
       SYNTAX      Counter32
       MAX-ACCESS  read-only
       STATUS      current
       DESCRIPTION
           "Total number of Proxy Binding Acknowledgement
            messages.
            Discontinuities in the value of this counter can
            occur at re-initialization of the management system,
            and at other times as indicated by the value of
            pmip6CounterDiscontinuityTime.
           "
       REFERENCE
           "RFC 5213: Sections 5.3.5"
           ::= { pmip6BindingRegCounters 16 }

   pmip6CounterDiscontinuityTime OBJECT-TYPE
       SYNTAX      TimeStamp
       MAX-ACCESS  read-only
       STATUS      current
       DESCRIPTION
           "The value of sysUpTime on the most recent occasion
            at which any one or more of this PMIPv6 entity's
            global counters, viz., counters with OID prefix
            'pmip6BindingRegCounters' suffered a discontinuity.
            If no such discontinuities have occurred since the
            last re-initialization of the local management
            subsystem, then this object will have a zero value.
           "
           ::= { pmip6BindingRegCounters 17 }

   pmip6LmaStatus OBJECT-TYPE
       SYNTAX      INTEGER { enabled(1), disabled(2) }
       MAX-ACCESS  read-write
       STATUS      current
       DESCRIPTION
           "This object indicates whether the PMIPv6 local


            mobility anchor function is enabled for the managed
            entity.

            Changing the status from enabled(1) to disabled(2)
            will terminate the PMIPv6 local mobility anchor
            function.  On the other hand, changing the status
            from disabled(2) to enabled(1) will start the PMIPv6
            local mobility anchor function.

            The value of this object MUST remain unchanged
            across reboots of the managed entity.
           "
       DEFVAL { disabled }
       ::= { pmip6LmaSystem 1 }

   pmip6LmaLMAATable OBJECT-TYPE
       SYNTAX      SEQUENCE OF Pmip6LmaLMAAEntry
       MAX-ACCESS  not-accessible
       STATUS      current
       DESCRIPTION
           "This table models the LMA Addresses configured
            on the local mobility anchor.  Each LMA Address acts as
            a transport endpoint of the tunnel between the local
            mobility anchor and the mobile access gateway and is
            the transport endpoint of the tunnel between the local
            mobility anchor and the mobile access gateway.

            Entries in this table are not required to survive
            a reboot of the managed entity.
           "
       REFERENCE
           "RFC 5213: Sections 2.2, 5.6"
       ::= { pmip6LmaSystem 2 }

   pmip6LmaLMAAEntry OBJECT-TYPE
       SYNTAX      Pmip6LmaLMAAEntry
       MAX-ACCESS  not-accessible
       STATUS      current
       DESCRIPTION
           "This entry represents a conceptual row in the
            LMAA table.  It represents each LMAA on the
            local mobility anchor.

            Implementers need to be aware that if the total
            number of octets in pmip6LmaLMAA exceeds 113,
            then OIDs of column instances in this row will
            have more than 128 sub-identifiers and cannot
            be accessed using SNMPv1, SNMPv2c, or SNMPv3.


           "
       INDEX  { pmip6LmaLMAAType, pmip6LmaLMAA }
       ::= { pmip6LmaLMAATable 1 }

   Pmip6LmaLMAAEntry ::=
       SEQUENCE {
        pmip6LmaLMAAType   InetAddressType,
        pmip6LmaLMAA       InetAddress,
        pmip6LmaLMAAState  INTEGER
       }

   pmip6LmaLMAAType OBJECT-TYPE
       SYNTAX      InetAddressType
       MAX-ACCESS  not-accessible
       STATUS      current
       DESCRIPTION
               "The InetAddressType of the pmip6LmaLMAA
                that follows.
               "
       ::= { pmip6LmaLMAAEntry 1 }

   pmip6LmaLMAA OBJECT-TYPE
       SYNTAX      InetAddress
       MAX-ACCESS  not-accessible
       STATUS      current
       DESCRIPTION
           "The LMAA configured on the local mobility anchor.

            The type of the address represented by this object
            is specified by the corresponding
            pmip6LmaLMAAType object.
           "
       REFERENCE
           "RFC 5213: Sections 2.2, 5.6"
       ::= { pmip6LmaLMAAEntry 2 }

   pmip6LmaLMAAState  OBJECT-TYPE
       SYNTAX      INTEGER {
                              unknown(1),
                              activated(2),
                              tunneled(3)
                      }
       MAX-ACCESS  read-only
       STATUS      current
       DESCRIPTION
           "This object indicates the state of the LMAA:
               unknown     -- The state of the LMAA
                              cannot be determined.


               activated   -- The LMAA is ready to establish
                              a tunnel.
               tunneled    -- The LMAA is used to set up the
                              bidirectional tunnel.
           "
       ::= { pmip6LmaLMAAEntry 3 }

   pmip6LmaMinDelayBeforeBCEDelete OBJECT-TYPE
       SYNTAX      Integer32 (1..65535)
       UNITS       "milliseconds"
       MAX-ACCESS  read-write
       STATUS      current
       DESCRIPTION
           "This variable specifies the length of time in
            milliseconds the local mobility anchor MUST wait before
            it deletes a Binding Cache entry of a mobile node, upon
            receiving a Proxy Binding Update message from a mobile
            access gateway with a lifetime value of 0.
            During this wait time, if the local mobility anchor
            receives a Proxy Binding Update for the same mobility
            binding, with a lifetime value greater than 0, then it
            must update the Binding Cache entry with the accepted
            binding values.  By the end of this wait time, if the
            local mobility anchor did not receive any valid Proxy
            Binding Update message for that mobility binding, it
            MUST delete the Binding Cache entry.  This delay
            essentially ensures that a mobile node's Binding Cache
            entry is not deleted too quickly and allows some time
            for the new mobile access gateway to complete the
            signaling for the mobile node.
            The default value for this variable is 10000
            milliseconds.
           "
       REFERENCE
           "RFC 5213: Sections 5.3.5, 9.1"
       DEFVAL { 10000 }
          ::= { pmip6LmaConf 1 }

   pmip6LmaMaxDelayBeforeNewBCEAssign OBJECT-TYPE
       SYNTAX      Integer32 (1..65535)
       UNITS       "milliseconds"
       MAX-ACCESS  read-write
       STATUS      current
       DESCRIPTION
           "This variable specifies the length of time in
            milliseconds the local mobility anchor MUST wait for
            the de-registration message for an existing mobility
            session before it decides to create a new mobility


            session.

            The default value for this variable is 1500
            milliseconds.  Note that there is a dependency between
            this value and the values used in the retransmission
            algorithm for Proxy Binding Updates.  The
            retransmissions need to happen before
            MaxDelayBeforeNewBCEAssign runs out, as otherwise there
            are situations where a de-registration from a previous
            mobile access gateway may be lost, and the local
            mobility anchor creates, needlessly, a new mobility
            session and new prefixes for the mobile node.  However,
            this affects situations where there is no information
            from the lower layers about the type of a handoff or
            other parameters that can be used for identifying the
            mobility session.
           "
       REFERENCE
           "RFC 5213: Sections 5.4.1.2, 5.4.1.3, 9.1"
       DEFVAL { 1500 }
          ::= { pmip6LmaConf 2 }
   pmip6LmaTimestampValidityWindow OBJECT-TYPE
       SYNTAX      Integer32 (1..65535)
       UNITS       "milliseconds"
       MAX-ACCESS  read-write
       STATUS      current
       DESCRIPTION
           "This variable specifies the maximum length of time
            difference in milliseconds between the timestamp in the
            received Proxy Binding Update message and the current
            time of day on the local mobility anchor that is
            allowed by the local mobility anchor for the received
            message to be considered valid.
            The default value for this variable is 300 milliseconds.
            This variable must be adjusted to suit the deployments.
           "
       REFERENCE
           "RFC 5213: Sections 5.5, 9.1"
       DEFVAL { 300 }
          ::= { pmip6LmaConf 3 }

   pmip6LmaMnIdentifierTable OBJECT-TYPE
       SYNTAX      SEQUENCE OF Pmip6LmaMnIdentifierEntry
       MAX-ACCESS  not-accessible
       STATUS      current
       DESCRIPTION
           "A table containing the identifiers of mobile nodes
            served by the LMA.


            Entries in this table are not required to survive
            a reboot of the managed entity.
           "
       REFERENCE
           "RFC 5213: Sections 2, 6.1"
       ::= { pmip6LmaConf 4 }

   pmip6LmaMnIdentifierEntry OBJECT-TYPE
       SYNTAX      Pmip6LmaMnIdentifierEntry
       MAX-ACCESS  not-accessible
       STATUS      current
       DESCRIPTION
           "An entry in the mobile node identifier table.
           "
       INDEX  { pmip6BindingMnIndex
              }
       ::= { pmip6LmaMnIdentifierTable 1 }

   Pmip6LmaMnIdentifierEntry ::=
       SEQUENCE {
        pmip6LmaMnIdentifier      Pmip6MnIdentifier
       }

   pmip6LmaMnIdentifier  OBJECT-TYPE
       SYNTAX      Pmip6MnIdentifier
       MAX-ACCESS  read-only
       STATUS      current
       DESCRIPTION
           "The identity of a mobile node in the Proxy Mobile IPv6
            domain.
           "
       REFERENCE
           "RFC 5213: Section 2.2"
       ::= { pmip6LmaMnIdentifierEntry 1 }

   pmip6LmaMnLLIdentifierTable OBJECT-TYPE
       SYNTAX      SEQUENCE OF Pmip6LmaMnLLIdentifierEntry
       MAX-ACCESS  not-accessible
       STATUS      current
       DESCRIPTION
           "A table containing the link-layer identifiers
            of the interfaces of the mobile nodes served
            by the LMA.
            Entries in this table are not required to survive
            a reboot of the managed entity.
           "
       REFERENCE
           "RFC 5213: Sections 2, 6.1"


       ::= { pmip6LmaConf 5 }

   pmip6LmaMnLLIdentifierEntry OBJECT-TYPE
       SYNTAX      Pmip6LmaMnLLIdentifierEntry
       MAX-ACCESS  not-accessible
       STATUS      current
       DESCRIPTION
           "An entry in the mobile node link-layer identifier
            table.
           "
       INDEX  { pmip6BindingMnIndex, pmip6BindingMnLLIndex
              }
       ::= { pmip6LmaMnLLIdentifierTable 1 }

   Pmip6LmaMnLLIdentifierEntry ::=
       SEQUENCE {
        pmip6LmaMnLLIdentifier      Pmip6MnLLIdentifier
       }

   pmip6LmaMnLLIdentifier  OBJECT-TYPE
        SYNTAX      Pmip6MnLLIdentifier
        MAX-ACCESS  read-only
        STATUS      current
        DESCRIPTION
            "The link-layer identifier of the mobile node's
             connected interface on the access link.
            "
        ::= { pmip6LmaMnLLIdentifierEntry 1 }

   pmip6LmaHomeNetworkPrefixTable   OBJECT-TYPE
        SYNTAX      SEQUENCE OF Pmip6LmaHomeNetworkPrefixEntry
        MAX-ACCESS  not-accessible
        STATUS      current
        DESCRIPTION
            "A table representing the home network prefixes
             assigned to the connected interfaces of all the
             mobile nodes anchored at the LMA.
            "
        REFERENCE
            "RFC 5213: Sections 2, 5.1, 5.2"
        ::= { pmip6LmaConf 6 }

   pmip6LmaHomeNetworkPrefixEntry OBJECT-TYPE
        SYNTAX      Pmip6LmaHomeNetworkPrefixEntry
        MAX-ACCESS  not-accessible
        STATUS      current
        DESCRIPTION
            "An entry in the home network prefixes table.


             Implementers need to be aware that if the total
             number of octets in pmip6LmaHomeNetworkPrefix
             exceeds 111 then OIDs of column instances in this
             row will have more than 128 sub-identifiers and
             cannot be accessed using SNMPv1, SNMPv2c, or
             SNMPv3.
            "
        INDEX  { pmip6BindingMnIndex, pmip6BindingMnLLIndex,
                 pmip6LmaHomeNetworkPrefixType,
                 pmip6LmaHomeNetworkPrefix }
        ::= { pmip6LmaHomeNetworkPrefixTable 1 }

   Pmip6LmaHomeNetworkPrefixEntry ::=
        SEQUENCE {
         pmip6LmaHomeNetworkPrefixType      InetAddressType,
         pmip6LmaHomeNetworkPrefix          InetAddress,
         pmip6LmaHomeNetworkPrefixLength    InetAddressPrefixLength,
         pmip6LmaHomeNetworkPrefixLifeTime  Gauge32
       }

   pmip6LmaHomeNetworkPrefixType  OBJECT-TYPE
        SYNTAX      InetAddressType
        MAX-ACCESS  not-accessible
        STATUS      current
        DESCRIPTION
            "The InetAddressType of the pmip6LmaHomeNetworkPrefix
             that follows.
            "
        ::= { pmip6LmaHomeNetworkPrefixEntry 1 }

   pmip6LmaHomeNetworkPrefix   OBJECT-TYPE
        SYNTAX      InetAddress
        MAX-ACCESS  not-accessible
        STATUS      current
        DESCRIPTION
            "The mobile network prefix that is delegated to the
             mobile node.  The type of the address represented by
             this object is specified by the corresponding
             pmip6LmaHomeNetworkPrefixType object.
            "
        REFERENCE
            "RFC 5213: Section 2"

        ::= { pmip6LmaHomeNetworkPrefixEntry 2 }

   pmip6LmaHomeNetworkPrefixLength   OBJECT-TYPE
        SYNTAX      InetAddressPrefixLength
        MAX-ACCESS  read-only


        STATUS      current
        DESCRIPTION
                "The prefix length of the home network prefix.
                "
        ::= { pmip6LmaHomeNetworkPrefixEntry 3 }

   pmip6LmaHomeNetworkPrefixLifeTime   OBJECT-TYPE
        SYNTAX      Gauge32
        UNITS       "seconds"
        MAX-ACCESS  read-write
        STATUS      current
        DESCRIPTION
            "The lifetime (in seconds) granted to the mobile
             node for this registration.
            "
        REFERENCE
            "RFC 5213: Section 5.3"
        ::= { pmip6LmaHomeNetworkPrefixEntry 4 }

   --
   -- pmip6Notifications
   --
   --

   pmip6MagHomeTunnelEstablished NOTIFICATION-TYPE
       OBJECTS   {
                   pmip6MagBLTunnelIfIdentifier,
                   pmip6MagProxyCOAState
                 }
       STATUS    current
       DESCRIPTION
           "This notification is sent by the Proxy Mobile IPv6
            entities every time the tunnel is established between
            the local mobility anchor and mobile access gateway.
           "
       REFERENCE
           "RFC 5213: Section 5.6.1"
           ::= { pmip6Notifications 1 }

   pmip6MagHomeTunnelReleased NOTIFICATION-TYPE
       OBJECTS {
                 pmip6MagBLTunnelIfIdentifier,
                 pmip6MagProxyCOAState
               }
       STATUS    current
       DESCRIPTION
           "This notification is sent by the Proxy Mobile IPv6
            entities every time the tunnel between the local


            mobility anchor and mobile access gateway is released.
           "
       REFERENCE
           "RFC 5213: Section 5.6.1"
           ::= { pmip6Notifications 2}

   pmip6LmaHomeTunnelEstablished NOTIFICATION-TYPE
       OBJECTS   {
                   pmip6BindingTunnelIfIdentifier,
                   pmip6LmaLMAAState
                 }
       STATUS    current
       DESCRIPTION
           "This notification is sent by the Proxy Mobile IPv6
            entities every time the tunnel is established between
            the local mobility anchor and mobile access gateway.
           "
       REFERENCE
           "RFC 5213: Section 5.6.1"
           ::= { pmip6Notifications 3 }

   pmip6LmaHomeTunnelReleased NOTIFICATION-TYPE
       OBJECTS {
                 pmip6BindingTunnelIfIdentifier,
                 pmip6LmaLMAAState
               }
       STATUS    current
       DESCRIPTION
           "This notification is sent by the Proxy Mobile IPv6
            entities every time the tunnel between the local
            mobility anchor and mobile access gateway is released.
           "
       REFERENCE
           "RFC 5213: Section 5.6.1"
           ::= { pmip6Notifications 4}

    -- Conformance information
   pmip6Groups      OBJECT IDENTIFIER ::= { pmip6Conformance 1 }
   pmip6Compliances OBJECT IDENTIFIER ::= { pmip6Conformance 2 }

    -- Units of conformance
   pmip6SystemGroup    OBJECT-GROUP
        OBJECTS {
            pmip6Capabilities,
            pmip6MobileNodeGeneratedTimestampInUse,
            pmip6FixedMagLinkLocalAddressOnAllAccessLinksType,
            pmip6FixedMagLinkLocalAddressOnAllAccessLinks,
            pmip6FixedMagLinkLayerAddressOnAllAccessLinks


       }
        STATUS  current
        DESCRIPTION
            " A collection of objects for basic PMIPv6
              monitoring."
        ::= { pmip6Groups 1 }

   pmip6BindingCacheGroup    OBJECT-GROUP
        OBJECTS {
            pmip6BindingPBUFlag,
            pmip6BindingMnIndex,
            pmip6BindingMnLLIndex,
            pmip6BindingMagLinkLocalAddressType,
            pmip6BindingMagLinkLocalAddress,
            pmip6BindingTunnelIfIdentifier,
            pmip6BindingMnInterfaceATT,
            pmip6BindingTimeRecentlyAccepted,
            pmip6LmaMnIdentifier,
            pmip6LmaMnLLIdentifier
       }
        STATUS  current
        DESCRIPTION
            " A collection of objects for monitoring the
              PMIPv6 extensions of the Binding Cache."
        ::= { pmip6Groups 2 }

   pmip6StatsGroup    OBJECT-GROUP
        OBJECTS {
            pmip6MissingMnIdentifierOption,
            pmip6MagNotAuthorizedForProxyReg,
            pmip6NotLMAForThisMobileNode,
            pmip6ProxyRegNotEnabled,
            pmip6MissingHomeNetworkPrefixOption,
            pmip6MissingHandOffIndicatorOption,
            pmip6MissingAccessTechTypeOption,
            pmip6NotAuthorizedForHomeNetworkPrefix,
            pmip6TimestampMismatch,
            pmip6TimestampLowerThanPrevAccepted,
            pmip6BcePbuPrefixSetDoNotMatch,
            pmip6InitialBindingRegistrations,
            pmip6BindingLifeTimeExtensionNoHandOff,
            pmip6BindingLifeTimeExtensionAfterHandOff,
            pmip6BindingDeRegistrations,
            pmip6BindingBindingAcks,
            pmip6CounterDiscontinuityTime
       }
        STATUS  current
        DESCRIPTION


            " A collection of objects for basic PMIPv6
              statistics monitoring.
            "
        ::= { pmip6Groups 3 }

   pmip6MagSystemGroup    OBJECT-GROUP
        OBJECTS {
          pmip6MagStatus,
          pmip6MagProxyCOAState
       }
        STATUS  current
        DESCRIPTION
            " A collection of objects for monitoring the
              PMIPv6-system-related objects on a mobile router."
        ::= { pmip6Groups 4 }

   pmip6MagConfigurationGroup    OBJECT-GROUP
        OBJECTS {
            pmip6MagHomeNetworkPrefixLength,
            pmip6MagHomeNetworkPrefixLifeTime,
            pmip6MagEnableMagLocalRouting
       }
        STATUS  current
        DESCRIPTION
            " A collection of objects for monitoring the
              configuration-related objects on a mobile access
              gateway.
            "
        ::= { pmip6Groups 5 }
   pmip6MagRegistrationGroup    OBJECT-GROUP
        OBJECTS {
            pmip6MagBLFlag,
            pmip6MagBLMnIndex,
            pmip6MagBLMnLLIndex,
            pmip6MagBLMagLinkLocalAddressType,
            pmip6MagBLMagLinkLocalAddress,
            pmip6MagBLMagIfIdentifierToMn,
            pmip6MagBLTunnelIfIdentifier,
            pmip6MagBLMnInterfaceATT,
            pmip6MagBLTimeRecentlyAccepted,
            pmip6MagMnIdentifier,
            pmip6MagMnLLIdentifier,
            pmip6MagProfMnIdentifier,
            pmip6MagProfMnLocalMobilityAnchorAddressType,
            pmip6MagProfMnLocalMobilityAnchorAddress
       }
        STATUS  current
        DESCRIPTION


            " A collection of objects for monitoring the
              registration-related objects on a mobile access
              gateway.
            "
        ::= { pmip6Groups 6 }

   pmip6LmaSystemGroup    OBJECT-GROUP
        OBJECTS {
            pmip6LmaStatus,
            pmip6LmaLMAAState
       }
        STATUS  current
        DESCRIPTION
            " A collection of objects for monitoring the
              system-related objects on an LMA."
        ::= { pmip6Groups 7 }

   pmip6LmaConfigurationGroup    OBJECT-GROUP
        OBJECTS {
            pmip6LmaMinDelayBeforeBCEDelete,
            pmip6LmaMaxDelayBeforeNewBCEAssign,
            pmip6LmaTimestampValidityWindow,
            pmip6LmaHomeNetworkPrefixLength,
            pmip6LmaHomeNetworkPrefixLifeTime
       }
        STATUS  current
        DESCRIPTION
            " A collection of objects for Monitoring the
              configuration-related objects on an LMA."
        ::= { pmip6Groups 8 }

   pmip6MagNotificationGroup   NOTIFICATION-GROUP
        NOTIFICATIONS {
                 pmip6MagHomeTunnelEstablished,
                 pmip6MagHomeTunnelReleased
       }
        STATUS  current
        DESCRIPTION
            "A collection of notifications from a home agent
             or correspondent node to the Manager about the
             tunnel status of the mobile router.
            "
        ::= { pmip6Groups 9 }

   pmip6LmaNotificationGroup   NOTIFICATION-GROUP
        NOTIFICATIONS {
                 pmip6LmaHomeTunnelEstablished,
                 pmip6LmaHomeTunnelReleased


       }
        STATUS  current
        DESCRIPTION
            "A collection of notifications from a home agent
             or correspondent node to the Manager about the
             tunnel status of the mobile router.
            "
        ::= { pmip6Groups 10 }

   -- Compliance statements
   pmip6CoreCompliance MODULE-COMPLIANCE
        STATUS  current
        DESCRIPTION
            "The compliance statement for SNMP entities
             that implement the PMIPV6-MIB.
             There are a number of INDEX objects that cannot be
             represented in the form of OBJECT clauses in
             SMIv2, but for which there are compliance
             requirements, expressed in OBJECT clause form in
             this description:
             -- OBJECT      pmip6BindingHomeAddressType
             -- SYNTAX      InetAddressType { ipv6(2) }
             -- DESCRIPTION
             --   This MIB module requires support for global
             --   ipv6 addresses for the pmip6BindingHomeAddress
             --   object.
             --
             "
        MODULE  -- this module
            MANDATORY-GROUPS { pmip6SystemGroup
                             }
        ::= { pmip6Compliances 1 }

   pmip6Compliance2 MODULE-COMPLIANCE
        STATUS  current
        DESCRIPTION
            "The compliance statement for SNMP entities
             that implement the PMIPV6-MIB.
             "
        MODULE  -- this module
            MANDATORY-GROUPS { pmip6SystemGroup,
                               pmip6BindingCacheGroup,
                               pmip6StatsGroup
                             }
        ::= { pmip6Compliances 2 }

   pmip6CoreReadOnlyCompliance MODULE-COMPLIANCE
        STATUS  current


        DESCRIPTION
            "The compliance statement for SNMP entities
             that implement the PMIPV6-MIB without support
             for read-write (i.e., in read-only mode).
             "
        MODULE  -- this module
            MANDATORY-GROUPS { pmip6SystemGroup
                             }
        OBJECT  pmip6MobileNodeGeneratedTimestampInUse
        MIN-ACCESS  read-only
        DESCRIPTION
               "Write access is not required."
        OBJECT  pmip6FixedMagLinkLocalAddressOnAllAccessLinksType
        MIN-ACCESS  read-only
        DESCRIPTION
               "Write access is not required."
        OBJECT  pmip6FixedMagLinkLocalAddressOnAllAccessLinks
        MIN-ACCESS  read-only
        DESCRIPTION
               "Write access is not required."
        OBJECT  pmip6FixedMagLinkLayerAddressOnAllAccessLinks
        MIN-ACCESS  read-only
        DESCRIPTION
               "Write access is not required."

        ::= { pmip6Compliances 3 }

   pmip6ReadOnlyCompliance2 MODULE-COMPLIANCE
        STATUS  current
        DESCRIPTION
            "The compliance statement for SNMP entities
             that implement the PMIPV6-MIB without support
             for read-write (i.e., in read-only mode).
             "
        MODULE  -- this module
            MANDATORY-GROUPS { pmip6SystemGroup,
                               pmip6BindingCacheGroup,
                               pmip6StatsGroup
                             }
        OBJECT  pmip6MobileNodeGeneratedTimestampInUse
        MIN-ACCESS  read-only
        DESCRIPTION
               "Write access is not required."
        OBJECT  pmip6FixedMagLinkLocalAddressOnAllAccessLinksType
        MIN-ACCESS  read-only
        DESCRIPTION
               "Write access is not required."
        OBJECT  pmip6FixedMagLinkLocalAddressOnAllAccessLinks


        MIN-ACCESS  read-only
        DESCRIPTION
               "Write access is not required."
        OBJECT  pmip6FixedMagLinkLayerAddressOnAllAccessLinks
        MIN-ACCESS  read-only
        DESCRIPTION
               "Write access is not required."

        ::= { pmip6Compliances 4 }

   pmip6MagCoreCompliance MODULE-COMPLIANCE
        STATUS  current
        DESCRIPTION
            "The compliance statement for SNMP entities
             that implement the PMIPV6-MIB.

             There are a number of INDEX objects that cannot be
             represented in the form of OBJECT clauses in
             SMIv2, but for which there are compliance
             requirements, expressed in OBJECT clause form in
             this description:
              -- OBJECT      pmip6MagProxyCOAType
              -- SYNTAX      InetAddressType { ipv6(2) }
              -- DESCRIPTION
              --     This MIB module requires support for global
              --     IPv6 addresses for the pmip6MagProxyCOAType
              --     object.
              --
              -- OBJECT      pmip6MagProxyCOA
              -- SYNTAX      InetAddress (SIZE(16))
              -- DESCRIPTION
              --     This MIB module requires support for global
              --     IPv6 addresses for the pmip6MagProxyCOA
              --     object.
              --
             "
        MODULE  -- this module
            MANDATORY-GROUPS { pmip6MagSystemGroup
                             }
        ::= { pmip6Compliances 5 }

   pmip6MagCompliance2 MODULE-COMPLIANCE
        STATUS  current
        DESCRIPTION
            "The compliance statement for SNMP entities that
             implement the PMIPV6-MIB for monitoring configuration-
             related information, registration details, and
             statistics on a mobile access gateway.


             There are a number of INDEX objects that cannot be
             represented in the form of OBJECT clauses in
             SMIv2, but for which there are compliance
             requirements, expressed in OBJECT clause form in
             this description:

              -- OBJECT      pmip6MagProxyCOAType
              -- SYNTAX      InetAddressType { ipv6(2) }
              -- DESCRIPTION
              --     This MIB module requires support for global
              --     IPv6 addresses for the pmip6MagProxyCOA
              --     object.
              --
              -- OBJECT      pmip6MagProxyCOA
              -- SYNTAX      InetAddress (SIZE(16))
              -- DESCRIPTION
              --     This MIB module requires support for global
              --     IPv6 addresses for the pmip6MagProxyCOAType
              --     object.
              --
              -- OBJECT      pmip6MagHomeNetworkPrefixType
              -- SYNTAX      InetAddressType { ipv6(2) }
              -- DESCRIPTION
              --     This MIB module requires support for global
              --     IPv6 addresses for the
              --     pmip6MagHomeNetworkPrefix object.
              --
              -- OBJECT      pmip6MagHomeNetworkPrefix
              -- SYNTAX      InetAddress (SIZE(16))
              -- DESCRIPTION
              --     This MIB module requires support for global
              --     IPv6 addresses for the
              --     pmip6MagHomeNetworkPrefix object.
              --
             "
        MODULE  -- this module
            MANDATORY-GROUPS { pmip6MagSystemGroup,
                               pmip6MagConfigurationGroup,
                               pmip6MagRegistrationGroup
                             }
        ::= { pmip6Compliances 6 }

   pmip6MagCoreReadOnlyCompliance MODULE-COMPLIANCE
        STATUS  current
        DESCRIPTION
            "The compliance statement for SNMP entities
             that implement the PMIPV6-MIB without support
             for read-write (i.e., in read-only mode).


             There are a number of INDEX objects that cannot be
             represented in the form of OBJECT clauses in
             SMIv2, but for which there are compliance
             requirements, expressed in OBJECT clause form in
             this description:
              -- OBJECT      pmip6MagProxyCOAType
              -- SYNTAX      InetAddressType { ipv6(2) }
              -- DESCRIPTION
              --     This MIB module requires support for global
              --     IPv6 addresses for the pmip6MagProxyCOA
              --     object.
              --
              -- OBJECT      pmip6MagProxyCOA
              -- SYNTAX      InetAddress (SIZE(16))
              -- DESCRIPTION
              --     This MIB module requires support for global
              --     IPv6 addresses for the pmip6MagProxyCOAType
              --     object.
              --
              -- OBJECT      pmip6MagHomeNetworkPrefixType
              -- SYNTAX      InetAddressType { ipv6(2) }
              -- DESCRIPTION
              --     This MIB module requires support for global
              --     IPv6 addresses for the
              --     pmip6MagHomeNetworkPrefix object.
              --
             "
        MODULE  -- this module
            MANDATORY-GROUPS { pmip6MagSystemGroup
                             }
        OBJECT  pmip6MagStatus
        MIN-ACCESS  read-only
        DESCRIPTION
               "Write access is not required."
        ::= { pmip6Compliances 7 }

   pmip6MagReadOnlyCompliance2 MODULE-COMPLIANCE
        STATUS  current
        DESCRIPTION
            "The compliance statement for SNMP entities that
             implement the PMIPV6-MIB without support for read-
             write (i.e., in read-only mode) and with support
             for monitoring configuration-related information,
             registration details, and statistics on a mobile
             access gateway.

             There are a number of INDEX objects that cannot be
             represented in the form of OBJECT clauses in


             SMIv2, but for which there are compliance
             requirements, expressed in OBJECT clause form in
             this description:

              -- OBJECT      pmip6MagProxyCOAType
              -- SYNTAX      InetAddressType { ipv6(2) }
              -- DESCRIPTION
              --     This MIB module requires support for global
              --     IPv6 addresses for the pmip6MagProxyCOA
              --     object.
              --
              -- OBJECT      pmip6MagProxyCOA
              -- SYNTAX      InetAddress (SIZE(16))
              -- DESCRIPTION
              --     This MIB module requires support for global
              --     IPv6 addresses for the pmip6MagProxyCOAType
              --     object.
              --
              -- OBJECT      pmip6MagHomeNetworkPrefixType
              -- SYNTAX      InetAddressType { ipv6(2) }
              -- DESCRIPTION
              --     This MIB module requires support for global
              --     IPv6 addresses for the
              --     pmip6MagHomeNetworkPrefix object.
              --
              -- OBJECT      pmip6MagHomeNetworkPrefix
              -- SYNTAX      InetAddress (SIZE(16))
              -- DESCRIPTION
              --     This MIB module requires support for global
              --     IPv6 addresses for the
              --     pmip6MagHomeNetworkPrefix object.
              --
             "
        MODULE  -- this module
            MANDATORY-GROUPS { pmip6MagSystemGroup,
                               pmip6MagConfigurationGroup,
                               pmip6MagRegistrationGroup
                             }
        OBJECT  pmip6MagStatus
        MIN-ACCESS  read-only
        DESCRIPTION
               "Write access is not required."
        OBJECT      pmip6MagEnableMagLocalRouting
        MIN-ACCESS  read-only
        DESCRIPTION
               "Write access is not required."

        ::= { pmip6Compliances 8 }


   pmip6LmaCoreCompliance MODULE-COMPLIANCE
        STATUS  current
        DESCRIPTION
            "The compliance statement for SNMP entities
             that implement the PMIPV6-MIB.
             There are a number of INDEX objects that cannot be
             represented in the form of OBJECT clauses in
             SMIv2, but for which there are compliance
             requirements, expressed in OBJECT clause form in
             this description:
              -- OBJECT      pmip6LmaLMAAType
              -- SYNTAX      InetAddressType { ipv6(2) }
              -- DESCRIPTION
              --     This MIB module requires support for global
              --     IPv6 addresses for the pmip6LmaLMAA
              --     object.
              --
              -- OBJECT      pmip6LmaLMAA
              -- SYNTAX      InetAddress (SIZE(16))
              -- DESCRIPTION
              --     This MIB module requires support for global
              --     IPv6 addresses for the pmip6LmaLMAA
              --     object.
              --
             "
        MODULE  -- this module
            MANDATORY-GROUPS { pmip6LmaSystemGroup
                             }
        ::= { pmip6Compliances 9 }

   pmip6LmaCompliance2 MODULE-COMPLIANCE
        STATUS  current
        DESCRIPTION
            "The compliance statement for SNMP entities that
             implement the PMIPV6-MIB for monitoring configuration-
             related information, registration details, and
             statistics on a mobile access gateway.

             There are a number of INDEX objects that cannot be
             represented in the form of OBJECT clauses in
             SMIv2, but for which there are compliance
             requirements, expressed in OBJECT clause form in
             this description:

              -- OBJECT      pmip6LmaLMAAType
              -- SYNTAX      InetAddressType { ipv6(2) }
              -- DESCRIPTION
              --     This MIB module requires support for global


              --     IPv6 addresses for the pmip6LmaLMAA
              --     object.
              --
              -- OBJECT      pmip6LmaLMAA
              -- SYNTAX      InetAddress (SIZE(16))
              -- DESCRIPTION
              --     This MIB module requires support for global
              --     IPv6 addresses for the pmip6LmaLMAA
              --     object.
              --
              -- OBJECT      pmip6LmaHomeNetworkPrefixType
              -- SYNTAX      InetAddressType { ipv6(2) }
              -- DESCRIPTION
              --     This MIB module requires support for global
              --     IPv6 addresses for the
              --     pmip6LmaHomeNetworkPrefix object.
              --
              -- OBJECT      pmip6LmaHomeNetworkPrefix
              -- SYNTAX      InetAddress (SIZE(16))
              -- DESCRIPTION
              --     This MIB module requires support for global
              --     IPv6 addresses for the
              --     pmip6LmaHomeNetworkPrefix object.
              --
             "
        MODULE  -- this module
            MANDATORY-GROUPS { pmip6LmaSystemGroup,
                               pmip6LmaConfigurationGroup
                             }
        ::= { pmip6Compliances 10 }

   pmip6LmaReadOnlyCompliance MODULE-COMPLIANCE
        STATUS  current
        DESCRIPTION
            "The compliance statement for SNMP entities
             that implement the PMIPV6-MIB.
             There are a number of INDEX objects that cannot be
             represented in the form of OBJECT clauses in
             SMIv2, but for which there are compliance
             requirements, expressed in OBJECT clause form in
             this description:
              -- OBJECT      pmip6LmaLMAAType
              -- SYNTAX      InetAddressType { ipv6(2) }
              -- DESCRIPTION
              --     This MIB module requires support for global
              --     IPv6 addresses for the pmip6LmaLMAA
              --     object.
              --


              -- OBJECT      pmip6LmaLMAA
              -- SYNTAX      InetAddress (SIZE(16))
              -- DESCRIPTION
              --     This MIB module requires support for global
              --     IPv6 addresses for the pmip6LmaLMAA
              --     object.
              --
             "
        MODULE  -- this module
            MANDATORY-GROUPS { pmip6LmaSystemGroup
                             }
        OBJECT  pmip6LmaStatus
        MIN-ACCESS  read-only
        DESCRIPTION
               "Write access is not required."
        ::= { pmip6Compliances 11 }

   pmip6LmaReadOnlyCompliance2 MODULE-COMPLIANCE
        STATUS  current
        DESCRIPTION
            "The compliance statement for SNMP entities that
             implement the PMIPV6-MIB without support
             for read-write (i.e., in read-only mode) and for
             monitoring configuration-related information,
             registration details, and statistics on a mobile
             access gateway.

             There are a number of INDEX objects that cannot be
             represented in the form of OBJECT clauses in
             SMIv2, but for which there are compliance
             requirements, expressed in OBJECT clause form in
             this description:

              -- OBJECT      pmip6LmaLMAAType
              -- SYNTAX      InetAddressType { ipv6(2) }
              -- DESCRIPTION
              --     This MIB module requires support for global
              --     IPv6 addresses for the pmip6LmaLMAA
              --     object.

              --
              -- OBJECT      pmip6LmaLMAA
              -- SYNTAX      InetAddress (SIZE(16))
              -- DESCRIPTION
              --     This MIB module requires support for global
              --     IPv6 addresses for the pmip6LmaLMAA
              --     object.
              --


              -- OBJECT      pmip6LmaHomeNetworkPrefixType
              -- SYNTAX      InetAddressType { ipv6(2) }
              -- DESCRIPTION
              --     This MIB module requires support for global
              --     IPv6 addresses for the
              --     pmip6LmaHomeNetworkPrefix object.
              --
              -- OBJECT      pmip6LmaHomeNetworkPrefix
              -- SYNTAX      InetAddress (SIZE(16))
              -- DESCRIPTION
              --     This MIB module requires support for global
              --     IPv6 addresses for the
              --     pmip6LmaHomeNetworkPrefix object.
              --
             "
        MODULE  -- this module
            MANDATORY-GROUPS { pmip6LmaSystemGroup,
                               pmip6LmaConfigurationGroup
                             }
        OBJECT  pmip6LmaStatus
        MIN-ACCESS  read-only
        DESCRIPTION
               "Write access is not required."
        OBJECT      pmip6LmaMinDelayBeforeBCEDelete
        MIN-ACCESS  read-only
        DESCRIPTION
               "Write access is not required."
        OBJECT      pmip6LmaMaxDelayBeforeNewBCEAssign
        MIN-ACCESS  read-only
        DESCRIPTION
               "Write access is not required."
        OBJECT      pmip6LmaTimestampValidityWindow
        MIN-ACCESS  read-only
        DESCRIPTION
               "Write access is not required."
        OBJECT      pmip6LmaHomeNetworkPrefixLifeTime
        MIN-ACCESS  read-only
        DESCRIPTION
               "Write access is not required."

        ::= { pmip6Compliances 12 }

   pmip6MagNotificationCompliance MODULE-COMPLIANCE
        STATUS  current
        DESCRIPTION
               "The compliance statement for SNMP entities that
                implement the PMIPV6-MIB and support notification
                from the mobile access gateway.


                "
        MODULE  -- this module
            MANDATORY-GROUPS { pmip6MagNotificationGroup
                             }
        ::= { pmip6Compliances 13 }

   pmip6LmaNotificationCompliance MODULE-COMPLIANCE
        STATUS  current
        DESCRIPTION
               "The compliance statement for SNMP entities that
                implement the PMIPV6-MIB and support notification
                from the LMA.
                "
        MODULE  -- this module
            MANDATORY-GROUPS { pmip6LmaNotificationGroup
                             }
        ::={  pmip6Compliances 14 }

   END
